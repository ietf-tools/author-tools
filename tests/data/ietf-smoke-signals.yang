module ietf-smoke-signals {
  yang-version 1.1;
  namespace "urn:ietf:params:xml:ns:yang:ietf-smoke-signals";
  prefix smoke;

  organization
    "IETF Author Tools Test";

  contact
    "WG Web:   <https://example.com/>
     WG List:  <mailto:example@example.com>

     Author:   Jane Doe
               <mailto:jdoe@example.com>";

  description
    "This module describes a smoke signal.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2024-01-01 {
    description
      "Initial revision.";
    reference
      "RFC XXXX: Smoke Signals";
  }

  container smoke-signals {
    description
      "Smoke signals.";
    leaf signal {
      type string;
      description
        "Smoke signal message.";
    }
  }
}
